APPD-CTLR-MIB DEFINITIONS ::= BEGIN

IMPORTS
	enterprises,
	MODULE-IDENTITY,
	OBJECT-TYPE,
	NOTIFICATION-TYPE
		FROM SNMPv2-SMI
	DisplayString,
	TimeStamp
		FROM SNMPv2-TC
	OBJECT-GROUP,
	NOTIFICATION-GROUP
		FROM SNMPv2-CONF
	snmpTrapAddress
		FROM SNMP-COMMUNITY-MIB;

appdMIB MODULE-IDENTITY
	LAST-UPDATED "201701030000Z"    -- January 3, 2016 12:00:00 AM
	ORGANIZATION "AppDynamics Inc"
	CONTACT-INFO
		"Not telling"
	DESCRIPTION
		"AppDynamics Trap MIB"
	REVISION "201701030000Z"    -- January 3, 2016 12:00:00 AM
	DESCRIPTION
		"Second Release - Three OID's"
	-- 1.3.6.1.4.1.40684.1.1
	::= { appDynamics1 1 }

appDynamics OBJECT IDENTIFIER ::= { enterprises 40684}

appDynamics1 OBJECT IDENTIFIER ::= { appDynamics 1 }

appd OBJECT IDENTIFIER
	-- 1.3.6.1.4.1.40684.1.1.1
	::= { appdMIB 1 }

eventData OBJECT IDENTIFIER
	-- 1.3.6.1.4.1.40684.1.1.1.1
	::= { appd 1 }

groups OBJECT IDENTIFIER
	-- 1.3.6.1.4.1.40684.1.1.1.200
	::= { appd 200 }

notifications OBJECT IDENTIFIER
	-- 1.3.6.1.4.1.40684.1.1.1.500
	::= { appd 500 }

appdNotifications NOTIFICATION-GROUP
        NOTIFICATIONS {
                policyOpen,
                policyClosed,
                nonPolicyEvent }
        STATUS  current
	DESCRIPTION
		"Notifications for events"
	-- 1.3.6.1.4.1.40684.1.1.1.200.1
	::= { groups 1 }

appdEventObjects OBJECT-GROUP
	OBJECTS {
		application,
		triggeredBy,
		nodes,
		txns,
		machines,
		tiers,
		eventTime,
		severity,
		type,
		subtype,
		summary,
		link,
		tag,
                eventType,
                ipAddresses,
                incidentId,
                 accountId}
	STATUS  current
	DESCRIPTION
		"Event attributes"
	-- 1.3.6.1.4.1.40684.1.1.1.200.2
	::= { groups 2 }


-- Notifications

policyOpen NOTIFICATION-TYPE
	OBJECTS {
		snmpTrapAddress,
		application,
		triggeredBy,
		nodes,
		txns,
		machines,
		tiers,
		eventTime,
		severity,
		type,
		subtype,
		summary,
		link,
		tag,
                eventType,
                ipAddresses,
                incidentId,
                 accountId}
	STATUS  current
	DESCRIPTION
		"Policy Open Notification"
	-- 1.3.6.1.4.1.40684.1.1.1.500.1
	::= { notifications 1 }

policyClosed NOTIFICATION-TYPE
	OBJECTS {
		snmpTrapAddress,
		application,
		triggeredBy,
		nodes,
		txns,
		machines,
		tiers,
		eventTime,
		severity,
		type,
		subtype,
		summary,
		link,
		tag,
                eventType,
                ipAddresses,
                incidentId,
                 accountId}
	STATUS  current
	DESCRIPTION
		"Policy Closed Notification"
	-- 1.3.6.1.4.1.40684.1.1.1.500.2
	::= { notifications 2 }


nonPolicyEvent NOTIFICATION-TYPE
	OBJECTS {
		snmpTrapAddress,
		application,
		triggeredBy,
		nodes,
		txns,
		eventTime,
		severity,
		type,
		subtype,
		summary,
		link,
		tag,
                eventType,
                incidentId,
                 accountId}
	STATUS  current
	DESCRIPTION
		"Informational Event Notification"
	-- 1.3.6.1.4.1.40684.1.1.1.500.3
	::= { notifications 3 }

-- Common

application OBJECT-TYPE
	SYNTAX  DisplayString (SIZE (0..255))
	MAX-ACCESS accessible-for-notify
	STATUS  current
	DESCRIPTION
		"Application name"
	-- 1.3.6.1.4.1.40684.1.1.1.1.1
	::= { eventData 1 }


triggeredBy OBJECT-TYPE
	SYNTAX  DisplayString (SIZE (0..255))
	MAX-ACCESS accessible-for-notify
	STATUS  current
	DESCRIPTION
		"Entities that triggered this event. Comma separated list"
	-- 1.3.6.1.4.1.40684.1.1.1.1.2
	::= { eventData 2 }


nodes OBJECT-TYPE
	SYNTAX  DisplayString (SIZE (0..255))
	MAX-ACCESS accessible-for-notify
	STATUS  current
	DESCRIPTION
		"Nodes that triggered this event. Comma separated list"
	-- 1.3.6.1.4.1.40684.1.1.1.1.3
	::= { eventData 3 }


txns OBJECT-TYPE
	SYNTAX  DisplayString (SIZE (0..255))
	MAX-ACCESS accessible-for-notify
	STATUS  current
	DESCRIPTION
		"Transactions that triggered this event. Comma separated list"
	-- 1.3.6.1.4.1.40684.1.1.1.1.4
	::= { eventData 4 }


machines OBJECT-TYPE
	SYNTAX  DisplayString (SIZE (0..255))
	MAX-ACCESS accessible-for-notify
	STATUS  current
	DESCRIPTION
		"Machines that triggered this event. Comma separated list of identifiers"
	-- 1.3.6.1.4.1.40684.1.1.1.1.5
	::= { eventData 5 }


tiers OBJECT-TYPE
	SYNTAX  DisplayString (SIZE (0..255))
	MAX-ACCESS accessible-for-notify
	STATUS  current
	DESCRIPTION
		"Tiers that triggered this event. Comma separated list"
	-- 1.3.6.1.4.1.40684.1.1.1.1.6
	::= { eventData 6 }


eventTime OBJECT-TYPE
	SYNTAX  TimeStamp
	MAX-ACCESS accessible-for-notify
	STATUS  current
	DESCRIPTION
		"Event time"
	-- 1.3.6.1.4.1.40684.1.1.1.1.7
	::= { eventData 7 }


severity OBJECT-TYPE
	SYNTAX  DisplayString (SIZE (0..255))
	MAX-ACCESS accessible-for-notify
	STATUS  current
	DESCRIPTION
		"Event severity ERROR, WARN, INFO"
	-- 1.3.6.1.4.1.40684.1.1.1.1.8
	::= { eventData 8 }


type OBJECT-TYPE
	SYNTAX  DisplayString (SIZE (0..255))
	MAX-ACCESS accessible-for-notify
	STATUS  current
	DESCRIPTION
		"Event type"
	-- 1.3.6.1.4.1.40684.1.1.1.1.9
	::= { eventData 9 }


subtype OBJECT-TYPE
	SYNTAX  DisplayString (SIZE (0..255))
	MAX-ACCESS accessible-for-notify
	STATUS  current
	DESCRIPTION
		"Event subtype"
	-- 1.3.6.1.4.1.40684.1.1.1.1.10
	::= { eventData 10 }


summary OBJECT-TYPE
	SYNTAX  DisplayString (SIZE (0..255))
	MAX-ACCESS accessible-for-notify
	STATUS  current
	DESCRIPTION
		"Event summary text"
	-- 1.3.6.1.4.1.40684.1.1.1.1.11
	::= { eventData 11 }


link OBJECT-TYPE
	SYNTAX  DisplayString (SIZE (0..255))
	MAX-ACCESS accessible-for-notify
	STATUS  current
	DESCRIPTION
		"Deep link to event"
	-- 1.3.6.1.4.1.40684.1.1.1.1.12
	::= { eventData 12 }

tag OBJECT-TYPE
        SYNTAX  DisplayString (SIZE (0..255))
        MAX-ACCESS accessible-for-notify
        STATUS  current
        DESCRIPTION
                "Tag of the event"
        -- 1.3.6.1.4.1.40684.1.1.1.1.13
        ::= { eventData 13 }

eventType OBJECT-TYPE
        SYNTAX  DisplayString (SIZE (0..255))
        MAX-ACCESS accessible-for-notify
        STATUS  current
        DESCRIPTION
                "Type of the event like POLICY_OPEN, POLICY_CLOSE etc"
        -- 1.3.6.1.4.1.40684.1.1.1.1.14
        ::= { eventData 14 }

ipAddresses OBJECT-TYPE
        SYNTAX  DisplayString (SIZE (0..255))
        MAX-ACCESS accessible-for-notify
        STATUS  current
        DESCRIPTION
                "IP Addresses for affected nodes"
        -- 1.3.6.1.4.1.40684.1.1.1.1.15
        ::= { eventData 15 }

incidentId OBJECT-TYPE
        SYNTAX  DisplayString (SIZE (0..255))
        MAX-ACCESS accessible-for-notify
        STATUS  current
        DESCRIPTION
                "The unique ID for the health rule violation"
        -- 1.3.6.1.4.1.40684.1.1.1.1.16
        ::= { eventData 16 }

accountId OBJECT-TYPE
        SYNTAX  DisplayString (SIZE (0..255))
        MAX-ACCESS accessible-for-notify
        STATUS  current
        DESCRIPTION
                "The accountId for the health rule violation. Useful for multi-tier host"
        -- 1.3.6.1.4.1.40684.1.1.1.1.17
        ::= { eventData 17 }

END
